module simple {
    namespace "my:namespace";
    prefix "simple";

    import b { prefix b; }

    grouping my-grouping {
        leaf-list my-grouping-leaf-list {
            type string;
        }
        leaf my-grouping-leaf {
           type string;
        }
    }

    container my-container {
        leaf my-attr {
            type string;
        }
        leaf-list my-array {
            type string;
        }
        container my-grouping-leaf {
          uses my-grouping;
        }
        container my-sub-container {
          leaf my-attr2 {
            type string;
          }
          leaf-list my-array2 {
            type string;
          }
        }
    }

  augment "/b:b-container/b:b-list" {
    leaf my-augmented-leaf {
      type string;
    }
  }
}
