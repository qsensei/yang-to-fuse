module b  {
    namespace "my:namespace:b";
    prefix "b";

    container b-container {
        list b-list {
            key "b-leaf";
            leaf b-leaf {
              type string;
            }
        }
    }
}
