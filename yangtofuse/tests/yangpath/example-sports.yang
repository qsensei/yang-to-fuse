module example-sports {

  namespace "http://example.com/example-sports";
  prefix sports;

  import example-stadium { prefix s; }
  import yang-ext { prefix ext; revision-date "2013-07-09";}

  typedef season {
    type string;
    description
      "The name of a sports season, including the type and the year, e.g,
       'Champions League 2014/2015'.";
  }

  grouping person-grouping {
      leaf birthday { type string; mandatory true; }
  }

  container sports {
    config true;

    list person {
      key name;
      leaf name { type string; }
      uses person-grouping;
    }

    list team {
      key name;
      leaf name { type string; }
      list player {
        key "name season";
        unique number;
        leaf name { type leafref { path "/sports/person/name"; }  }
        leaf season { type season; }
        leaf number { type uint16; mandatory true; }
        leaf scores { type uint16; default 0; }
      }
    }
  }

  augment "/s:stadium" {
    leaf occupancy { type uint32; }
  }
  augment "/s:stadium/s:location" {
    ext:augment-identifier "sports-augment";
    leaf gdp { type uint32; }

    container politics {
      leaf-list parties {
        type string;
      }
    }
  }
}
